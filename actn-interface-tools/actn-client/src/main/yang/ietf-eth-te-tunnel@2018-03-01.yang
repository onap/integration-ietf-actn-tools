module ietf-eth-te-tunnel {
//	yang-version 1.1;

        namespace "urn:ietf:params:xml:ns:yang:ietf-eth-te-tunnel";

        prefix "eth-tunnel";

        import ietf-te {
                prefix "te";
        }

        import ietf-eth-tran-types {
                prefix "etht-types";
        }

        organization
                "Internet Engineering Task Force (IETF) CCAMP WG";
  contact
    "
      WG List: <mailto:ccamp@ietf.org>

      ID-draft editor:
        Haomian Zheng (zhenghaomian@huawei.com);
        Italo Busi (italo.busi@huawei.com);
        Aihua Guo (aihuaguo@huawei.com);
        Yunbin Xu (xuyunbin@ritt.cn);
        Yang Zhao (zhaoyangyjy@chinamobile.com);
        Xufeng Liu (Xufeng_Liu@jabil.com);
        Giuseppe Fioccola (giuseppe.fioccola@telecomitalia.it);
    ";

        description
                "This module defines a model for ETH transport tunnel";

        revision 2018-03-01 {
                description
                        "Initial revision";
                reference
                        "draft-zheng-ccamp-client-tunnel-yang-02";
        }

        grouping eth-tunnel-endpoint {
                description "Parameters for ETH tunnel.";

                leaf vlanid {
                        type etht-types:vlanid;
                        description
                                "VLAN tag id.";
                }

                leaf tag-type {
                        type etht-types:eth-tag-type;
                        description "VLAN tag type.";
                }
        }

        augment "/te:te/te:tunnels/te:tunnel" {
                description
                        "Augment with additional parameters required for ETH
                        service.";

                container src-eth-tunnel-endpoint {
                        description
                                "Source ETH tunnel endpoint.";
                        uses eth-tunnel-endpoint;
                }

                container dst-eth-tunnel-endpoint {
                        description
                                "Destination ETH tunnel endpoint.";

                        uses eth-tunnel-endpoint;
                }

                container bandwidth-profile {
                        description
                                "ETH tunnel bandwidth profile specification.";

                        uses etht-types:etht-bandwidth-profiles;
                }
        }
}
